module sfc-openstack {
    namespace "urn:cisco:params:xml:ns:yang:sfc-openstack";
    prefix sfc-openstack;

    import ietf-inet-types {
            prefix inet;
            revision-date 2013-07-15;
        }
    import ietf-yang-types {
        prefix yang;
        revision-date 2013-07-15;
        }

    organization "openstack Systems, Inc.";
    description
        "this is openstack sfc";

    revision 2016-12-18 {
        description
            "sfc-openstack revision";
        reference
            "sfc-yang";
        }

    grouping sfp-point {
        leaf index {
            type uint32 {
                range "0..16777216";
            }
        }
        leaf port-name {
            type string;
            mandatory true;
            description "port name";
        }
        leaf node-ip {
            type string;
            mandatory true;
            default "172.31.0.3";
            description "the point's node ip address";
        }
    }

    grouping ip-match {
        leaf src-ip {
            type string;
            default "192.168.1.2/32";
        }
        leaf dst-ip {
            type string;
            default "192.168.1.3/32";
        }
        leaf protocol-name {
            type string;
            default "icmp";
            description "match protocol name";
        }
        leaf port {
            type inet:port-number;
            default 0;
        }
    }

    grouping sfc-base {
        leaf name {
            type string;
            mandatory true;
            default "mysfc";
        }
        leaf description {
            type string;
            default "this is a service function chain description";
        }
        container sfc-bridge {
            leaf converge-bridge-name {
                type string;
                mandatory true;
                default "br-int";
            }
            leaf tunnel-bridge-name {
                type string;
                mandatory true;
                default "br-sfc";
            }
        }
        leaf sfc-nsp {
            type uint32 {
                range "0..9527";
            }
            mandatory true;
            default 12;
        }
        container sfp-entries {
            container source {
                uses sfp-point;
            }
            container sfp-sf-entries{
                list sfp-sf-entry {
                    key "index";
                    uses sfp-point;
                    leaf sf-mac {
                        type yang:mac-address;
                        mandatory true;
                    }
                }
            }
            container destination {
                uses sfp-point;
            }
        }
        container sfc-match {
            uses ip-match;
        }
    }
    container sfc-entries {
        list sfc-entry {
            key "sfc-nsp";
            uses sfc-base;
        }
    }

    rpc put-sfc {
        input {
            uses sfc-base;
        }
    }

    rpc delete-sfc {
        input {
            leaf name {
                type string;
                mandatory true;
            }
        }
    }

}
